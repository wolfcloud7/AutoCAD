(defun C:PIRAMIDE()
  (command "_OSMODE" 0)
  (command "_SURFTAB1" 12)
  (command "_SURFTAB2" 12)
  (command "_ISOLINES" 12)
  (setq base  (getpoint "Esquina de la pirámide: "))
  (setq lados (getint "Lados: "))
  (setq altura (getint "Altura: "))
  (setq anchobase  (getint "Ancho base: "))
  (command "_PYRAMID" "s" lados base anchobase altura)
  )
