(defun c:LINTERNA()
  (command "_OSMODE" 0)
  (command "_SURFTAB1" 12)
  (command "_SURFTAB2" 12)
  (command "_ISOLINES" 12)
  ;
  (setq base (getpoint "BASE LINTERNA: "))  
  (command "_CYLINDER" base 20 20)
  (setq x (entlast))
  (setq p1 (list (+ 20 (nth 0 base)) (nth 1 base) (nth 2 base) ))
  (command "_CYLINDER" p1 3 20)
  (setq a (entlast))
  (command "_ARRAYPOLAR" a "" base "i" 15 "" "exit" "")
  (setq b (entlast))
  (command "explode" b)  
  (setq c (ssget "p"))
  (command "_SUBTRACT" base "" c "" "")
  ;
  (setq p2 (list (nth 0 base) (nth 1 base) (+ (nth 2 base) 20) ))
  (command "_SPHERE" p2 20)
  (setq esfera1 (entlast))
  (command "_CYLINDER" base 20 20)
  (setq a (entlast))
  (command "_SUBTRACT" esfera1 "" a "" "")
  (command "_CYLINDER" p2 10 60)
  (setq a (entlast))
  (command "_UNION" esfera1 a "")
  ;
  (setq p3 (list (nth 0 base) (nth 1 base)  (+ (nth 2 base) 80) ))
  (command "_SPHERE" p3 10)
  (setq esfera2 (entlast))
  (command "_CYLINDER" p2 10 60)
  (setq a (entlast))
  (command "_SUBTRACT" esfera2 "" a "" "")
  (command "_CYLINDER" p3 2 18)
  (setq b (entlast))
  ;
  (setq p4 (list (nth 0 base) (nth 1 base)  (+ (nth 2 base) 98) ))
  (command "_SPHERE" p4 2)
  (setq esfera3(entlast))
  (command "_UNION" esfera3 b esfera2 "")
  ;
  (setq p5 (list (nth 0 p3) (- (nth 1 p3) 2 ) (- (nth 2 p3) 2 ) ))
  (setq p6 (list (+ 15 (nth 0 p5)) (+ (nth 1 p5)4)(- (nth 2 p5) 2 ) ))
  (command "_BOX" p5 p6)
  (setq manija1 (entlast))
  ;
  (setq p7 (list (- (nth 0 p6) 2 ) (- (nth 1 p6) 4) (- (nth 2 p6 )20) ))
  (command "_BOX" p6 p7)
  (setq manija2 (entlast))
  ;
  (command "_UNION" manija1 manija2 "")
)
